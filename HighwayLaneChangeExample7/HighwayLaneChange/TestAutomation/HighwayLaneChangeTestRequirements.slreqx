# HighwayLaneChangeTestRequirements

## #1: scenario_LC_01_SlowMoving (Functional)
| Test Description | Target vehicles | Requirements on Ego vehicle |
| --- | --- | --- |
| Lane change test with a slow-moving lead vehicle on a straight road.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 | Lead vehicle: Initial velocity: 10m/s Headway: 130m Event: The lead vehicle travels in ego lane with a constant velocity of 10m/s. | Initial velocity: 20m/s Longitudinal Jerk < 5 m/s^3 Lateral Jerk < 5 m/s^3 Time gap > 0.8s Front Safety Gap >20m Rear Safety Gap > 5m TTC in the Ego Lane > 2 TTC in the next lane > 5 Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: Ego vehicle should perform lane change to avoid collision with a slow-moving lead vehicle while using the specified planner configuration. |

## #2: scenario_LC_02_SlowMovingWithPassingCar (Functional)
| Test Description | Target vehicles | Requirements on Ego vehicle |
| --- | --- | --- |
| Lane change test with a slow-moving lead vehicle on a straight road with a passing car.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 | Lead vehicle: Initial velocity: 10m/s Headway: 130m Event: The lead vehicle travels in the ego lane with a constant velocity of 10m/s. | Initial velocity: 20m/s Longitudinal Jerk < 5 m/s^3 Lateral Jerk < 5 m/s^3 Time gap > 0.8s Front Safety Gap >20m Rear Safety Gap > 5m TTC in the Ego Lane > 2 TTC in the next lane > 5 Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: Ego vehicle should perform lane change to avoid collision with the slow-moving lead vehicle while negotiating with a passing vehicle. |

## #3: scenario_LC_03_DisabledCar (Functional)
| Test Description | Target vehicles | Requirements on Ego vehicle |
| --- | --- | --- |
| Lane change test with breakdown vehicle on a straight road.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 | Lead vehicle: Initial velocity: 9m/s Headway: 130m Event: The vehicle in the ego lane is a breakdown vehicle. The vehicle remains in the same position. Passing vehicle: Set velocity: 33m/s Headway: -40m Lane: Ego left lane | Initial velocity: 20m/s Longitudinal Jerk < 5 m/s^3 Lateral Jerk < 5 m/s^3 Time gap > 0.8s Front Safety Gap >20m Rear Safety Gap > 5m TTC in the Ego Lane > 2 TTC in the next lane > 5 Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: The ego vehicle should perform a lane change to avoid collision with a slow-moving lead vehicle while negotiating with the fast-moving passing vehicle in the left lane. |

## #4: scenario_LC_04_CutInWithBrake (Functional)
| Test Description | Target vehicles | Requirements on Ego vehicle |
| --- | --- | --- |
| Lane change test with a cut-in vehicle on a straight road.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 | Breakdown lead vehicle: Initial velocity: ~0m/s Headway: 240m Event: Cut-in vehicle starts its travels in ego right lane. Then, to avoid collision with a slow-moving vehicle it cuts into ego lane and then decelerates to 10 m/s at 8s. | Initial velocity: 14m/s Longitudinal Jerk < 5 m/s^3 Lateral Jerk < 5 m/s^3 Time gap > 0.8s Front Safety Gap >20m Rear Safety Gap > 5m TTC in the Ego Lane > 2 TTC in the next lane > 5 Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: Ego vehicle should avoid collision with the breakdown vehicle in its lane by performing a lane change. |

## #5: scenario_LC_05_SingleLaneChange (Functional)
| Test Description | Target vehicles | Requirements on Ego vehicle |
| --- | --- | --- |
| Single lane change test on a straight road.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 | Lead vehicle: Initial velocity: 10m/s Headway: 90m Event: The lead vehicle starts with an initial velocity of 10 m/s and starts decelerating at 1s in the ego lane. Fast-moving rear vehicle: The fast-moving rear vehicle is in the left lane of the ego lane and moves with a constant velocity of 34 m/s. Fast-moving front car: The fast-moving front car is in the right lane of the ego lane and moves with a constant velocity of 17m/s. | Initial Velocity: 25m/s Longitudinal Jerk < 5 m/s^3 Lateral Jerk < 5 m/s^3 Time gap > 0.8s Front Safety Gap >20m Rear Safety Gap > 5m TTC in the Ego Lane > 2 TTC in the next lane > 5 Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: The ego vehicle should respond to a slow-moving lead vehicle that is present in its lane while negotiating with the fast-moving rear vehicle in the left lane and the fast-moving front vehicle in the right lane. The ego vehicle should perform lane change to avoid collision with the lead vehicle along with other vehicles in the scenario. |

## #6: scenario_LC_06_DoubleLaneChange (Functional)
| Test Description | Target vehicles | Requirements on Ego vehicle |
| --- | --- | --- |
| Double lane change test on a straight road.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 | Lead vehicle: Initial velocity: 18m/s Headway: 90m Event: The lead vehicle starts with an initial velocity of 10 m/s and starts decelerating at 1s in the ego lane. Fast-moving rear vehicle: Initial velocity: 34 m/s Headway: -60m Event: The fast-moving rear vehicle is in the left lane of the ego lane and moves with a constant velocity of 34 m/s. Fast Moving front vehicle: Initial velocity: 17 m/s Headway: 14m Event: The fast-moving front vehicle is in the right lane of the ego lane and moves with a constant velocity of 17 m/s. Fast-moving rear vehicle2: Initial velocity: 20 m/s Headway: -100m Event: The fast-moving rear vehicle is in the left lane of the ego lane and moves with a constant velocity of 20 m/s. | Initial velocity: 15 m/s Longitudinal Jerk < 5 m/s^3 Lateral Jerk < 5 m/s^3 Time gap > 0.8s Front Safety Gap >20m Rear Safety Gap > 5m TTC in the Ego Lane > 2 TTC in the next lane > 5 Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: The ego vehicle should avoid collision with the slow-moving lead vehicle. It also performs lane change again to avoid collision with the fast-moving rear vehicle. |

## #7: scenario_LC_07_RightLaneChange (Functional)
| Test Description | Target vehicles | Requirements on Ego vehicle |
| --- | --- | --- |
| Right lane change test on a straight road.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 | Lead vehicle: Initial Velocity: 10m/s Headway: 120m Event: The lead vehicle is traveling with a constant velocity of 10 m/s in the ego lane. Fast-moving front left vehicle: Initial Velocity: 25m/s Headway: 50m Event: The fast-moving front left vehicle is traveling with a constant velocity of 25 m/s in the left lane of the ego lane. Fast-moving rear left vehicle: Initial Velocity: 10m/s Headway: -40m Event: The fast-moving rear left vehicle is traveling in the left lane of ego lane with an initial velocity of 24 m/s and starts decelerating at around 5s | Initial Velocity: 20m/s Longitudinal Jerk < 5 m/s^3 Lateral Jerk < 5 m/s^3 Time gap > 0.8s Front Safety Gap >20m Rear Safety Gap > 5m TTC in the Ego Lane > 2 TTC in the next lane > 5 Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: Ego vehicle should perform a right lane change to avoid collision with other vehicles in the scenario. |

## #8: scenario_LC_08_SlowmovingCar_Curved (Functional)
| Test Description | Target vehicles | Requirements on Ego vehicle |
| --- | --- | --- |
| Lane change test with a slow-moving vehicle on a curved road.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 | Lead vehicle: Initial velocity: 10m/s Headway: 130m Event: The lead vehicle moves at a constant velocity of 10 m/s | Initial velocity: 20m/s Longitudinal Jerk < 5 m/s^3 Lateral Jerk < 5 m/s^3 Time gap > 0.8s Front Safety Gap >20m Rear Safety Gap > 5m TTC in the Ego Lane > 2 sec TTC in the next lane > 5 sec Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: The ego vehicle should perform lane change to avoid collision with a slow-moving lead vehicle on a curved road. |

## #9: scenario_LC_09_CutInWithBrake_Curved (Functional)
| Test Description | Target vehicles | Requirements on Ego vehicle |
| --- | --- | --- |
| Lane change test with a cut-in vehicle on a curved road.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 | Breakdown lead vehicle: Initial velocity: ~0m/s Headway: 240m Event: Cut-in vehicle starts its travels in ego right lane. Then, to avoid collision with a slow-moving vehicle it cuts into ego lane and then decelerates to 10 m/s at 8s. | Initial velocity: 14m/s Longitudinal Jerk < 5 m/s^3 Lateral Jerk < 5 m/s^3 Time gap > 0.8s Front Safety Gap >20m Rear Safety Gap > 5m TTC in the Ego Lane > 2 sec TTC in the next lane > 5 sec Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: Ego vehicle should avoid collision with the breakdown vehicle in its lane by performing a lane change. |

## #10: scenario_LC_10_SingleLaneChange_Curved (Functional)
| Test Description | Target vehicles | Requirements on Ego vehicle |
| --- | --- | --- |
| Single lane change test on a curved road.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 | Lead vehicle: Initial velocity: 10m/s Headway: 90m Event: The lead vehicle starts with an initial velocity of 10 m/s and starts decelerating at 1s in the ego lane. Fast-moving rear vehicle: The fast-moving rear vehicle is in the left lane of the ego lane and moves with a constant velocity of 34 m/s. Fast-moving front car: The fast-moving front car is in the right lane of the ego lane and moves with a constant velocity of 17m/s. | Initial Velocity: 25m/s Longitudinal Jerk < 5 m/s^3 Lateral Jerk < 5 m/s^3 Time gap > 0.8s Front Safety Gap >20m Rear Safety Gap > 5m TTC in the Ego Lane > 2 sec TTC in the next lane > 5 sec Planner Configuration: Time Horizon = 1:3; Time Resolution = 0.1; Preferred Lane = 3; Set Speed = 15m/s; Lateral Deviation Cost = 1.0; Time Cost = -1.0; Speed Cost = 1.0; Max Acceleration = 5.0m/s^2; Max Curvature = 1.0; Min Velocity = 0m/s; Max Yaw Rate = 80.0; Enable Cruise, Lead Car following and Lane change behaviors. Expected behavior: The ego vehicle should respond to a slow-moving lead vehicle that is present in its lane while negotiating with the fast-moving rear vehicle in the left lane and the fast-moving front vehicle in the right lane. The ego vehicle should perform lane change to avoid collision with the lead vehicle along with other vehicles in the scenario while using the specified planner configuration. |

## #11: scenario_LC_11_MergingCar_HighwayEntry (Functional)
| Test Description | Target vehicles | Requirements on Ego vehicle |
| --- | --- | --- |
| Lane change test with merging vehicle on highway entry scene.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 | Merging vehicle: Initial velocity: 15m/s Event: Merging vehicle starts moving into ego lane from highway entry at 5s with a constant velocity of 15 m/s. Fast-moving rear vehicle: The fast-moving rear vehicle is in the left lane of the ego lane and moves with a constant velocity of 33 m/s. | Initial Velocity: 20m/s Longitudinal Jerk < 5 m/s^3 Lateral Jerk < 5 m/s^3 Time gap > 0.8s Front Safety Gap >20m Rear Safety Gap > 5m TTC in the Ego Lane > 2 sec TTC in the next lane > 5 sec Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: Ego vehicle should respond to merging vehicle and perform a lane change while negotiating with the fast moving rear vehicle. |

## #12: scenario_LC_12_CutInCar_HighwayEntry (Functional)
| Test Description | Target vehicles | Requirements on Ego vehicle |
| --- | --- | --- |
| Lane change test with cut-in vehicle on highway entry scene.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 | Cut-in vehicle: Initial velocity: 15m/s Headway: 70m Event: Cut-in vehicle starts to move into ego lane at 5 s with constant velocity of 15 m/s. Fast moving rear vehicle: Initial velocity: 10m/s Headway: -30m The fast-moving rear vehicle is in the left lane of ego lane and moves with a constant velocity of 33 m/s. | Initial Velocity: 20m/s Longitudinal Jerk < 5 m/s^3 Lateral Jerk < 5 m/s^3 Time gap > 0.8s Front Safety Gap >20m Rear Safety Gap > 5m TTC in the Ego Lane > 2 sec TTC in the next lane > 5 sec Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: Ego vehicle should respond to cut-in vehicle and perform a lane change while negotiating with other vehicles in the scenario. |

## #13: scenario_LC_13_DisabledCar_Ushape (Functional)
| Test Description | Target vehicles | Requirements on Ego vehicle |
| --- | --- | --- |
| Lane change test with disabled car on U-shaped Road.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 | Lead vehicle: Initial velocity: 10m/s Headway: 45m Event: Lead vehicle moves with constant velocity of 10 m/s Slow-moving left front vehicle: The slow-moving left front vehicle moves with constant velocity of 6 m/s. Break down vehicle in the left lane: The break down vehicles stays in the left lane of ego vehicle. | Initial Velocity: 11m/s Longitudinal Jerk < 5 m/s^3 Lateral Jerk < 5 m/s^3 Time gap > 0.8s Front Safety Gap >20m Rear Safety Gap > 5m TTC in the Ego Lane > 2 sec TTC in the next lane > 5 sec Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: The ego vehicle should respond to slow-moving lead vehicle that is present in its lane while negotiating with other vehicles in the scenario. |

## #14: scenario_LC_14_DoubleLaneChange_Ushape (Functional)
| Test Description | Target vehicles | Requirements on Ego vehicle |
| --- | --- | --- |
| Double Lane change test with disabled car on U-shaped Road.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 | Lead vehicle: Initial velocity: 10m/s Headway: 45m Event: Lead vehicle moves with constant velocity of 10 m/s Slow-moving left front vehicle: The slow-moving left front vehicle moves with constant velocity of 6 m/s. Break down vehicle in the left lane: The break down vehicles stays in the left lane of ego vehicle. | Initial Velocity: 11m/s Longitudinal Jerk < 5 m/s^3 Lateral Jerk < 5 m/s^3 Time gap > 0.8s Front Safety Gap >20m Rear Safety Gap > 5m TTC in the Ego Lane > 2 sec TTC in the next lane > 5 sec Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: The ego vehicle should perform lane change once to avoid collision with lead vehicle and it must perform another lane change to avoid collision with a disabled car in the new lane. |

## #15: scenario_LC_15_StopnGo_Curved (Functional)
| Test Description | Target vehicles | Requirements on Ego vehicle |
| --- | --- | --- |
| Lane change test with slow moving lead vehicle on a curved road.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 | Lead vehicle: Initial velocity: 10m/s Headway: 45m Event: Lead vehicle moves with constant velocity of 10 m/s Slow-moving left front vehicle: The slow-moving left front vehicle moves with constant velocity of 6 m/s. Break down vehicle in the right lane: The break down vehicles stays in the right lane of ego vehicle. | Initial Velocity: 11m/s Longitudinal Jerk < 5 m/s^3 Lateral Jerk < 5 m/s^3 Time gap > 0.8s Front Safety Gap >20m Rear Safety Gap > 5m TTC in the Ego Lane > 2 sec TTC in the next lane > 5 sec Planner Configuration: Time Horizon = 1:3 sec; Time Resolution = 0.1 sec; Preferred Lane = 2; Set Speed = 20 m/s; Lateral Deviation Cost = 1.0; Time Cost = -1.0; Speed Cost = 1.0; Max Acceleration = 5.0 m/s^2; Max Curvature = 1.0 m^-1; Min Velocity = 0 m/s; Max Yaw Rate = 80.0 rad/sec; Enable Cruise, Lead Car following and Lane change behaviors. Expected behavior: The ego vehicle should respond to slow-moving lead vehicle that is present in its lane while negotiating with other vehicles in the scenario. |
